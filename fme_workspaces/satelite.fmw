FME workspace satelite.fmw

Parameters:
- SourceDataset_POSTGIS = TIIG   # Connection
- DestDataset_POSTGIS = TIIG   # Connection

Readers:
- POSTGIS_1: POSTGIS from $(SourceDataset_POSTGIS)

Writers:
- POSTGIS_2: POSTGIS to $(DestDataset_POSTGIS)

embalses_geom (reader POSTGIS_1)
    attributes: fid serial,PrimaryKey, timestamp timestamptz, cuenca varchar, cuenca_norm varchar, pantano varchar, capacidad int8, embalsada varchar, variacion varchar
    -> Reprojector
Reprojector
    DEST = EPSG:4326
    INTERPOLATION_TYPE = NearestNeighbor
    RASTER_CELL_SIZE = PreserveCells
    RASTER_TOLERANCE = 0.0
    SOURCE = EPSG:25830
    REPROJECTED -> BoundsExtractor
BoundsExtractor
    XMAX = _xmax
    XMIN = _xmin
    YMAX = _ymax
    YMIN = _ymin
    ZMAX = _zmax
    ZMIN = _zmin
    -> GeometryExtractor
GeometryExtractor
    ATTR = aoi_geojson
    JSON_MAX_DIGITS = 7
    KIND = GEOJSON
    REMOVE_GEOMETRY = No
    KIND_LONG = GeoJSON
    -> JSONTemplater [ROOT]
JSONTemplater
    RESULT_ATTRIBUTE = _result
    ROOT_QUERY_EXPR:
      {
        "collections": ["sentinel-2-l2a"],
        "datetime": "2024-12-01T00:00:00Z/2026-12-30T23:59:59Z",
        "intersects": fme:get-json-attribute("aoi_geojson"),
        "limit": 5,
        "query": {
          "eo:cloud_cover": {
            "lt": 10
          }
        }
      }
    VISIBLE_QUERY_VALIDATE = Yes
    -> HTTPCaller
HTTPCaller
    CLIENT_CERTIFICATE_TYPE = NONE
    CONNECTION_TIMEOUT_LENGTH = 60
    CONTENT_TYPE_LOOKUP = application/json
    CUSTOM_HEADERS = Content-Type;application/json
    ERROR_ATTR = _error
    FOLLOW_REDIRECTS = FOLLOW_WITH_GET
    HTTP_METHOD = POST
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://earth-search.aws.element84.com/v1/search
    TRANSFER_TIMEOUT_LENGTH = 90
    UPLOAD_BODY = @Value(_result)
    UPLOAD_TYPE = STRING_UPLOAD
    USE_COOKIES = No
    VERIFY_SSL_CERTIFICATES = Yes
    UPLOAD_CONTENT_TYPE = JSON (application/json)
    -> JSONFragmenter
JSONFragmenter
    EXPLODE_FORMAT = JSON
    EXTRACT_ATTR = Yes
    INPUT_PORT_CONNECTED = CONNECTED
    JSON_ATTR = _response_body
    JSON_QUERY = json["features"][*]
    READ_FROM_FILE = NO
    RECURSIVE = YES
    REJECT_EMPTY_LISTS = YES
    FRAGMENTS -> JSONFlattener
JSONFlattener
    ERROR_LIST_ATTR = _json_error
    INPUT_PORT_CONNECTED = CONNECTED
    JSON_DOCUMENT = @Value(_response_body)
    NEW_ATTRIBUTES = assets.visual.href buffer properties.eo:cloud_cover buffer
    READ_FROM_FILE = NO
    RECURSIVE = YES
    -> Sorter
Sorter
    GROUP_BY = fid
    SORT_PARM = properties.eo:cloud_cover NUMERIC ASCENDING NON_VALUES_AFTER_VALUES
    SORTED -> Sampler_2
Sampler_2
    GROUP_BY = fid
    MODE = ORIGINAL
    RATE = 1
    SAMPLE_TYPE_MULTIPLIER = -1
    SAMPLE_MODE = No
    SAMPLE_TYPE_LONG = First N Features
    SAMPLED -> AttributeRenamer
AttributeRenamer
    ATTR_TABLE = RENAME_SET_DEFAULT assets.visual.href > url_descarga
    KEEP_RENAMED_ONLY = no
    MISSING_INPUT_ATTRS = REMOVE
    -> StringReplacer
StringReplacer
    CASE = NO
    NO_MATCH = _FME_NO_OP_
    REGEXP = NO
    STR_REPLACE_TABLE = url_descarga s3:// https://s3.eu-central-1.amazonaws.com/
    -> embalses_geom (writer POSTGIS_2)
embalses_geom (writer POSTGIS_2)
    attributes: url_descarga varchar, fid serial,PrimaryKey
